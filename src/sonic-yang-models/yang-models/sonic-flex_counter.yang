module sonic-flex_counter {

    yang-version 1.1;

    namespace "http://github.com/Azure/sonic-flex_counter";
    prefix flex_counter;

    description "FLEX COUNTER YANG Module for SONiC OS";

    revision 2020-04-10 {
        description "First Revision";
    }

    container sonic-flex_counter {

        container FLEX_COUNTER_TABLE {

            /* typedef specific to FLEX_COUNTER_TABLE */
            typedef flex_status {
                type enumeration {
                    enum enable;
                    enum disable;
                }
            }

            description "FLEX_COUNTER_TABLE part of config_db.json";

            /* below are in alphabetical order */

            container BUFFER_POOL_WATERMARK {
                /* BUFFER_POOL_WATERMARK_STAT_COUNTER_FLEX_COUNTER_GROUP */
                leaf FLEX_COUNTER_STATUS {
                    type flex_status;
                }
            }

            container DEBUG_COUNTER {
                /* DEBUG_COUNTER_FLEX_COUNTER_GROUP */
                leaf FLEX_COUNTER_STATUS {
                    type flex_status;
                }
            }

            container PFCWD {
                /* PFC_WD_FLEX_COUNTER_GROUP */
                leaf FLEX_COUNTER_STATUS {
                    type flex_status;
                }
            }

            container PG_WATERMARK {
                /* PG_WATERMARK_STAT_COUNTER_FLEX_COUNTER_GROUP */
                leaf FLEX_COUNTER_STATUS {
                    type flex_status;
                }
            }

            container PG_DROP {
                /* PG_DROP_STAT_COUNTER_FLEX_COUNTER_GROUP */
                leaf FLEX_COUNTER_STATUS {
                    type flex_status;
                }
            }

            container PORT {
                /* PORT_STAT_COUNTER_FLEX_COUNTER_GROUP */
                leaf FLEX_COUNTER_STATUS {
                    type flex_status;
                }
            }

            container PORT_RATES {
                /* PORT_BUFFER_DROP_COUNTER_FLEX_COUNTER_GROUP */
                leaf FLEX_COUNTER_STATUS {
                    type flex_status;
                }
            }

            container PORT_BUFFER_DROP {
                /* PORT_BUFFER_DROP_COUNTER_FLEX_COUNTER_GROUP */
                leaf FLEX_COUNTER_STATUS {
                    type flex_status;
                }
            }

            container QUEUE {
                /* QUEUE_STAT_COUNTER_FLEX_COUNTER_GROUP */
                leaf FLEX_COUNTER_STATUS {
                    type flex_status;
                }
            }

            container QUEUE_WATERMARK {
                /* QUEUE_WATERMARK_STAT_COUNTER_FLEX_COUNTER_GROUP */
                leaf FLEX_COUNTER_STATUS {
                    type flex_status;
                }
            }

            container RIF {
                /* RIF_STAT_COUNTER_FLEX_COUNTER_GROUP */
                leaf FLEX_COUNTER_STATUS {
                    type flex_status;
                }
            }

            container RIF_RATES {
                /* RIF_RATE_COUNTER_FLEX_COUNTER_GROUP */
                leaf FLEX_COUNTER_STATUS {
                    type flex_status;
                }
            }

        }
        /* end of container FLEX_COUNTER_TABLE */
    }
    /* end of top level container */
}
/* end of module sonic-flex_counter */
